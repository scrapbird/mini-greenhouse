# -*- coding: utf-8 -*-
# Close the greenhouse: set all door/hatch parts to canonical closed
# placements (computed from Dims) and remove the hatch prop. Idempotent.

import FreeCAD, math

doc = FreeCAD.ActiveDocument
if doc is None:
    raise RuntimeError("No active document")
ss = doc.Dims


def compute_closed_placements(ss):
    W = float(ss.Width); D = float(ss.Depth); H_ext = float(ss.Height)
    PX = float(ss.PostX); PY = float(ss.PostY)
    RT = float(ss.RailT); RW = float(ss.RailW)
    DFT = float(ss.DoorFrameT); DFW = float(ss.DoorFrameW)
    PT = float(ss.PanelThk)
    overhang_f = float(ss.RoofOverhangF)
    R = float(ss.RoofRise); roof_thk = float(ss.RoofThk)

    ang = math.atan2(R, D); cos_a = math.cos(ang); tan_a = math.tan(ang)
    H_b = H_ext - roof_thk * cos_a
    H_f = H_b - R
    H_f_wall = H_f - RW/cos_a

    door_clear = 3.0
    door_total_w = (W - 2*PX) / 2 - door_clear
    door_total_h = (H_f_wall - 2*RW) - door_clear
    door_z0 = RW + door_clear/2
    x_L = PX + door_clear/2
    x_R = x_L + door_total_w + door_clear
    infill_y0 = (DFW - PT) / 2
    astragal_w = 30.0
    bolt_w = 25.0; bolt_h = 100.0
    bolt_x = x_L + door_total_w - DFT - bolt_w - 10

    rot_x = FreeCAD.Rotation(FreeCAD.Vector(1, 0, 0), math.degrees(ang))
    I = FreeCAD.Rotation()

    rafter_base_z = H_f_wall + (-overhang_f) * R / D
    ridge_base_y = D - RT * cos_a
    ridge_base_z = H_f_wall + ridge_base_y * R / D

    def P(x, y, z, rot=I):
        return FreeCAD.Placement(FreeCAD.Vector(x, y, z), rot)

    return {
        "DoorL_StileHinge": P(x_L, 0, door_z0),
        "DoorL_StileLatch": P(x_L + door_total_w - DFT, 0, door_z0),
        "DoorL_RailTop":    P(x_L + DFT, 0, door_z0 + door_total_h - DFT),
        "DoorL_RailBot":    P(x_L + DFT, 0, door_z0),
        "DoorL_Infill":     P(x_L + DFT, infill_y0, door_z0 + DFT),
        "DoorL_Astragal":   P(x_L + door_total_w - astragal_w/2, -12.0, door_z0),
        "DoorL_BoltTop":    P(bolt_x, DFW, door_z0 + door_total_h - bolt_h - 20),
        "DoorL_BoltBot":    P(bolt_x, DFW, door_z0 + 20),
        "DoorR_StileHinge": P(x_R, 0, door_z0),
        "DoorR_StileLatch": P(x_R + door_total_w - DFT, 0, door_z0),
        "DoorR_RailTop":    P(x_R + DFT, 0, door_z0 + door_total_h - DFT),
        "DoorR_RailBot":    P(x_R + DFT, 0, door_z0),
        "DoorR_Infill":     P(x_R + DFT, infill_y0, door_z0 + DFT),
        "DoorR_Latch":      P(x_R + DFT + 5, DFW, door_z0 + door_total_h/2 - 40),
        "Roof_Hatch":        P(0, -overhang_f, H_f - overhang_f * tan_a, rot_x),
        "Frame_RafterLeft":   P(0, -overhang_f, rafter_base_z, rot_x),
        "Frame_RafterRight":  P(W - RT, -overhang_f, rafter_base_z, rot_x),
        "Frame_RafterCenter": P((W - RT)/2, -overhang_f, rafter_base_z, rot_x),
        "Frame_EaveFront":    P(RT, -overhang_f, rafter_base_z, rot_x),
        "Frame_RidgeBack":    P(RT, ridge_base_y, ridge_base_z, rot_x),
    }


placements = compute_closed_placements(ss)
for name, pl in placements.items():
    obj = doc.getObject(name)
    if obj is not None:
        obj.Placement = pl

for n in ["Hatch_Prop", "Hatch_PropBracketBot", "Hatch_PropBracketTop"]:
    if doc.getObject(n):
        doc.removeObject(n)

doc.recompute()
FreeCAD.Console.PrintMessage("gh_close: done\n")
